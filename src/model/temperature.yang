module temperature {
  yang-version 1.1;
  namespace "urn:test:interfaces:temperature";
  prefix tempif;

  container interface {
    list sensor {
      key "name";
      leaf name {
        type string;
      }
      leaf enabled {
        type boolean;
        default "true";
      }
    }
  }
}
